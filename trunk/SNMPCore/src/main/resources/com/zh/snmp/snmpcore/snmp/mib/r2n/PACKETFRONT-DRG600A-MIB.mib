PACKETFRONT-DRG600A-MIB DEFINITIONS ::= BEGIN

-- Copyright (c) 2007,2008,2009 Packetfront Systems AB

IMPORTS
  MODULE-IDENTITY,
  OBJECT-TYPE,
  NOTIFICATION-TYPE,
  Integer32
    FROM SNMPv2-SMI

  pfMgmt
    FROM PACKETFRONT-SMI

  InterfaceIndex
    FROM IF-MIB

  productMacAddress,
  productIdentity
    FROM PACKETFRONT-DRG-MIB
;


-- *****************************************************************************
-- drg600aMIB defines the platform-specific objects for the DRG600 Access module
--
-- ***************************************************************************** 
pfDrg600aMib MODULE-IDENTITY
    LAST-UPDATED "200903231559Z"
    ORGANIZATION "PacketFront Systems AB"
    CONTACT-INFO
        "PacketFront Systems AB
         Customer Service

         Mail : Isafjordsgatan 35
                SE-164 28 Kista
                Sweden

         Tel  : +46 8 5090 1500

         E-mail: snmp@packetfront.com
         Web   : http://www.packetfront.com"
    DESCRIPTION
        "The MIB module for managing Packetfront DRG devices"

    REVISION    "200903231559Z" -- March 23, 2009
    DESCRIPTION
        "Updated telephone information in contact-info"
    REVISION    "200712190000Z" -- December 19, 2007
    DESCRIPTION
        "Initial release."

      ::= { pfMgmt 7 }


drg600aNotification OBJECT IDENTIFIER ::= { pfDrg600aMib 0 }
drg600aConfig       OBJECT IDENTIFIER ::= { pfDrg600aMib 1 }
drg600aConformance  OBJECT IDENTIFIER ::= { pfDrg600aMib 2 }


-- *****************************************************************************
-- Base 
--
-- *****************************************************************************
drg600aBaseConfig OBJECT IDENTIFIER ::= {drg600aConfig 1} 

drg600aFiberTransceiverCap OBJECT-TYPE
  SYNTAX BITS {
    transceiverNotFiber(0),
    transceiver100M(1),
    transceiver1000M(2)
  } 
  MAX-ACCESS read-only
  STATUS current
  DESCRIPTION
  "Flag field which describes the fiber transceiver capabilities"
    ::= { drg600aBaseConfig 1 }

drg600aModuleStatus OBJECT-TYPE
  SYNTAX BITS {
    module1(0),
    module2(1),
    module3(2)
  } 
  MAX-ACCESS read-only
  STATUS current
  DESCRIPTION
  "Flag field which indicates the presence or not of modules attached to the
  DRG600 access device. A '1' indicates that a module is present, while a '0'
  indicates that no module is present.
  Module1, module2, and module3 are the left-hand, right-hand, and downward 
  modules respectively."
    ::= { drg600aBaseConfig 2 }

drg600aSnmpAtomicSet OBJECT-TYPE
  SYNTAX INTEGER {
    idle(1),
    stage(2),
    apply(3)
  }
  MAX-ACCESS read-write
  STATUS current
  DESCRIPTION
  "Complex operations involving numerous set commands can cause problems due
  to the lack of atomic operation by the network management system. This object
  may be used to ensure that all required changes for this MIB are made in a
  single atomic operation.
   This can be achieved by setting this object to stage(2), then setting all
  required objects, and then setting this object to apply(3). The object value
  will return to idle(1) once the atomic set operation has been completed."
    ::= { drg600aBaseConfig 3 }



-- *****************************************************************************
-- Information about Ethernet ports.
--
-- *****************************************************************************
drg600aPortConfig OBJECT IDENTIFIER ::= {drg600aConfig 2} 

drg600aPortNumPorts OBJECT-TYPE
   SYNTAX Integer32
   MAX-ACCESS read-only
   STATUS current
   DESCRIPTION
  "Number of ports in the bridge."
    ::= { drg600aPortConfig 1 }

drg600aPortTable OBJECT-TYPE
   SYNTAX SEQUENCE OF Drg600aPortEntry
   MAX-ACCESS   not-accessible
   STATUS       current
   DESCRIPTION
      "A list of port entries."
     ::= { drg600aPortConfig 3 }

drg600aPortEntry OBJECT-TYPE
   SYNTAX Drg600aPortEntry
   MAX-ACCESS not-accessible
   STATUS current
   DESCRIPTION
   "An entry containing information for a particular switched port. The
   number of entries is fixed by the platform, and are not created or deleted
   by a management entity."
   INDEX { drg600aPortIndex }
   ::= { drg600aPortTable 1 }

Drg600aPortEntry ::=
    SEQUENCE {
     drg600aPortIndex InterfaceIndex,
-- can do the same job with ifDescr, but this can be a functional name, e.g. VoIP, Wifi etc
     drg600aPortName OCTET STRING,
     drg600aPortDuplexAdmin INTEGER,
     drg600aPortDuplexStatus INTEGER,
     drg600aPortFlowControlAdmin INTEGER,
     drg600aPortFlowControlStatus INTEGER,
     drg600aPortSpeedAdmin INTEGER,
     drg600aPortIgmpSnoop INTEGER,
     drg600aPortVlanMode INTEGER,
     drg600aPortVlanEgressMode INTEGER,
     drg600aPortVlanId INTEGER,
     drg600aPortVlanPriority INTEGER,
     drg600aPortSubscriberTagType INTEGER,
     
-- QoS classification
    drg600aPortQoSVTUPriorityOverride INTEGER,
    drg600aPortQoSIPPriorityOverride INTEGER,
    drg600aPortQoSVlanPriorityOverride INTEGER,
    drg600aPortQueueNumber Integer32,
    drg600aPortQueueAlgorithm INTEGER,
    drg600aPortMacAddressLimitMax Integer32,
    drg600aPortMacAddressLimit Integer32,
     
-- storm protection & rate limiting
    drg600aPortIngressRateLimitControl INTEGER,
    drg600aPortRateLimitIngress INTEGER,
    drg600aPortRateLimitEgress INTEGER

-- Error thresholds
--    drg600aPortCRCErrorThreshold INTEGER,

-- Port VLANs
--     drg600aPortVlanGroupSupport INTEGER,
--     drg600aPortVlanGroupMembershipTable INTEGER
  }

drg600aPortIndex OBJECT-TYPE
   SYNTAX InterfaceIndex
   MAX-ACCESS read-only
   STATUS current
   DESCRIPTION
      "A unique value greater than zero for each port."
   ::= { drg600aPortEntry 1 }

drg600aPortName OBJECT-TYPE
   SYNTAX OCTET STRING  (SIZE(0..32))
-- If this is not different to ifName what is its point?
   MAX-ACCESS read-only
   STATUS current
   DESCRIPTION
   "A textual string containing name specifying the port. This may be used as a
   functional hint or to indicate the service etc."
   ::= { drg600aPortEntry 2 }

drg600aPortDuplexAdmin OBJECT-TYPE
  SYNTAX INTEGER {
    halfDuplex(1),
    fullDuplex(2)
  }
  MAX-ACCESS read-write
  STATUS current
  DESCRIPTION
  "The required duplex mode of the port"
    ::= { drg600aPortEntry 3 }

drg600aPortDuplexStatus OBJECT-TYPE
    SYNTAX INTEGER {
      halfDuplex(1),
      fullDuplex(2)
    }
    MAX-ACCESS read-only
    STATUS current
    DESCRIPTION
    "The current duplex status of the port - if the port is in autonegotiation
    mode, then this will reflect the negotiated duplex, else the configure duplex."
      ::= { drg600aPortEntry 4 }

drg600aPortFlowControlAdmin OBJECT-TYPE
    SYNTAX INTEGER {
      enabled(1),
      disabled(2)
    }
    MAX-ACCESS read-write
    STATUS current
    DESCRIPTION
    "Controls the required flow control mode of the port"
      ::= { drg600aPortEntry 5 }

drg600aPortFlowControlStatus OBJECT-TYPE
    SYNTAX INTEGER {
      enabled(1),
      disabled(2)
    }
    MAX-ACCESS read-only
    STATUS current
    DESCRIPTION
    "The current flow control status of the port - if the port is in autonegotiation
    mode, then this will reflect the negotiated flow control state, else the configured state duplex."
    ::= { drg600aPortEntry 6 }

drg600aPortSpeedAdmin OBJECT-TYPE
  SYNTAX INTEGER {
    autoNegotiate(1),
    s10e06(10000000),
    s100e06(100000000)
  }
  MAX-ACCESS read-write
  STATUS current
  DESCRIPTION
  "The object controls the speed of the port, and whether autonegotiation is
  used with the link partner. If autoNegotiate(1) is used, then the device will
  use the Ethernet autonegotiate procedure to determine the link configuration.
  However, if a speed is configured, the autonegotiate will not be used the
  speed, duplex and flow control will be determined by their relevant objects."
    ::= { drg600aPortEntry 7 }

drg600aPortIgmpSnoop OBJECT-TYPE
  SYNTAX INTEGER {
    enabled(1),
    disabled(2)
  }
  MAX-ACCESS read-write
  STATUS current
  DESCRIPTION
  "Defines whether IGMP snooping shall be performed on the port. If enabled,
  IGMP frames received are forwarded to the CPU for processing. Valid IGMP
  messages will cause multicast entries to be made in the forwarding
  table, the forwarded upstream to any IGMP multicast routers"
    ::= { drg600aPortEntry 8 }

drg600aPortVlanMode OBJECT-TYPE
    SYNTAX INTEGER {
      disabled(1),
      secure(2),
      check(3),
      fallback(4)
    }
    MAX-ACCESS read-write
    STATUS current
    DESCRIPTION
    "This object determines the VLAN ingress and egress policy for a port.

    disabled - VLAN tags are not checked, this allows frames which are tagged or
               untagged to ingress or egress the port.
    secure - if supported, on ingress the frame VLAN idenfifier must be 
             contained within VLAN table, and the port must be a member of the
             VLAN. On egress, the port must be a member of the VLAN, and be
             included in the same port VLAN group as the ingress port.
    check  - if supported, on ingress the frame VLAN identifier must be
             contained within the VLAN table.  On egress, the port must be a 
             member of the VLAN, and be included in the same port VLAN group as
             the ingress port.
    fallback - if supported, no check is performed on ingress. On egress, the
               port must be included in the same port VLAN group as the ingress
               port."
      ::= { drg600aPortEntry 9 }

drg600aPortVlanEgressMode OBJECT-TYPE
  SYNTAX INTEGER {
    unmodified(1),
    tag(2),
    untag(3),
    alwaysTagged(4)
  }
  MAX-ACCESS read-write
  STATUS current
  DESCRIPTION
  "This object determines the port egress behaviour.
    unmodified - Frames egress the port in an unmodified state, i.e. remain
                 tagged or untagged depending upon their state on ingress.
    tag        - Untagged frames are tagged with the ingress port default VID.
    untag      - Tagged frames are untagged.
    alwaysTagged - Frames egressing the port are tagged with the ingress port
                 subscriber tag. In the case where a VLAN tagged frame is
                 egressing the port, this results in the frame being double, or
                 Q-in-Q tagged"
    ::= { drg600aPortEntry 10 }


-- *****************************************************************************
-- Port VLAN configuration
--
-- *****************************************************************************
drg600aPortVlanId OBJECT-TYPE
    SYNTAX Integer32 (0..4094)
    MAX-ACCESS read-write
    STATUS current
    DESCRIPTION
    "If the object value is between 0 and 4094, untagged packets received on 
    this port are associated with this VLAN ID if tagging is enabled on the 
    egress port. In the case of a value of 0, this is the null VLAN ID and
    indicates that the header contains only priority information; no VLAN
    identifier will be present in the frame."
      ::= { drg600aPortEntry 11 }

drg600aPortVlanPriority OBJECT-TYPE
    SYNTAX Integer32 (0..7)
    MAX-ACCESS read-write
    STATUS current
    DESCRIPTION
    "Untagged packets received on this port are associated with this VLAN
    priority if tagging is enabled on the egress port."
      ::= { drg600aPortEntry 12 }

drg600aPortSubscriberTagType OBJECT-TYPE
    SYNTAX Integer32 (0..65535)
    MAX-ACCESS read-write
    STATUS current
    DESCRIPTION
    "The subscriber tag (S-Tag) ether type applied to frames if VLAN stacking
     and is enabled."
    DEFVAL { 37120 }  -- 0x9100
      ::= { drg600aPortEntry 13 }


-- *****************************************************************************
-- Port QoS configuration
--
-- *****************************************************************************
drg600aPortQoSVTUPriorityOverride OBJECT-TYPE
    SYNTAX INTEGER {
      enabled(1),
      disabled(2)
    }
    MAX-ACCESS read-write
    STATUS current
    DESCRIPTION
    "When enabled(1) the ingressing frame VLAN priority may, if permitted, be 
    overridden by the priority value of the assigned VLAN entry."
      ::= { drg600aPortEntry 14 }

drg600aPortQoSIPPriorityOverride OBJECT-TYPE
    SYNTAX INTEGER {
      enabled(1),
      disabled(2)
    }
    MAX-ACCESS read-write
    STATUS current
    DESCRIPTION
    "When enabled(1) use the IPv4 TOS and/or Diffserv fields and/or IPv6
    traffic class fields for priority data"
      ::= { drg600aPortEntry 15 }

drg600aPortQoSVlanPriorityOverride OBJECT-TYPE
    SYNTAX INTEGER {
      enabled(1),
      disabled(2)
    }
    MAX-ACCESS read-write
    STATUS current
    DESCRIPTION
    "When enabled(1) and the ingressing frame is IEEE802.1ac tagged, use the
    IEEE802.1p traffic class field for priority data."
      ::= { drg600aPortEntry 16 }


drg600aPortQueueNumber OBJECT-TYPE
  SYNTAX Integer32
  MAX-ACCESS read-only
  STATUS current
  DESCRIPTION
  "The number of queues supported by this port"
    ::= { drg600aPortEntry 17 }

drg600aPortQueueAlgorithm OBJECT-TYPE
  SYNTAX INTEGER {
    strictPriorityQueue(1), 
    weightedFairQueue(2)
  }
  MAX-ACCESS   read-write
  STATUS       current
  DESCRIPTION
  "Defines the queueing algorithm that is to be used on the port. strictPriority-
   Queue(1) means that the high priority queue always get served when it contains
   frames and that the low priority queue is served only when no high priority 
   frames are present. weightedFairQueue(2) means that high priority queues are 
   processed before low priority queues, and that a specified number of frames 
   are transmitted from any queue at one time. In this way, all queues are 
   processed so that no queue is blocked by higher priority traffic"
    ::= { drg600aPortEntry 18 }

drg600aPortMacAddressLimitMax OBJECT-TYPE
    SYNTAX Integer32
    MAX-ACCESS read-only
    STATUS current
    DESCRIPTION
    "Indicates the maximum number of addresses which can be stored in the address 
    table for the port. A value of 0 indicates that setting a limit is not supported"
    ::= { drg600aPortEntry 19 }

drg600aPortMacAddressLimit OBJECT-TYPE
    SYNTAX Integer32
    MAX-ACCESS read-write
    STATUS current
    DESCRIPTION
    "Controls the maximum MAC addresses that may be stored in the address table for a
    port. This has the effect of limiting the number of endpoints which may be
    simultaneously connected to a port. 0 indicates that the limit is whatever is
    supported in hardware, while any other value indicates the maximum number of
    addresses"
    ::= { drg600aPortEntry 20 }

-- *****************************************************************************
-- Port xcast storm protection and rate limit configuration
--
-- *****************************************************************************
drg600aPortIngressRateLimitControl OBJECT-TYPE
  SYNTAX INTEGER {
    limitAll(1),
    limitMBU(2),
    limitMB(3),
    limitBroadcast(4)
  }
  MAX-ACCESS read-write
  STATUS current
  DESCRIPTION
  "Controls what type of traffic is ingress rate limited. limitAll(1) applies
  the limit to all traffic types, limitMBU(2) applies the limit to multicast,
  broadcast and flooded unicast. limitMB(3) applies the limit to multicast and
  broadcast traffic, and limitBroadcast(4) limits the ingress rate of broadcast
  frames.
  Note that flooded unicast refers to unicast traffic where the destination
  address is unknown, so frames are flooded to all ports except the ingress
  port."
    ::= { drg600aPortEntry 21 }

drg600aPortRateLimitIngress OBJECT-TYPE
  SYNTAX Integer32 (0..1000000000)
  UNITS "bits per second"
  MAX-ACCESS read-write
  STATUS current
  DESCRIPTION
  "Defines the maximum ingress rate in bits per second. This is best used for
   storm protection, and not TCP/IP rate limiting. The actual rate used is
   hardware dependant, and will be approximated from the value defined. The
   value should not be greater than the maximum rate of the interface. If it is
   then the value shall be ignored, and no rate limit will be applied.
   Use a value of 0 to disable rate limiting"
    ::= { drg600aPortEntry 22 }

drg600aPortRateLimitEgress OBJECT-TYPE
  SYNTAX Integer32 (0..1000000000)
  UNITS "bits per second"
  MAX-ACCESS read-write
  STATUS current
  DESCRIPTION
  "Defines the maximum egress rate in bits per second. This is best used for
   storm protection, and not TCP/IP rate limiting. The actual rate used is
   hardware dependant, and will be approximated from the value defined. The
   value should not be greater than the maximum rate of the interface. If it is
   then the value shall be ignored, and no rate limit will be applied.
   Use a value of 0 to disable rate limiting"
    ::= { drg600aPortEntry 23 }


-- *****************************************************************************
-- Port error threshold
--
-- *****************************************************************************
--drg600aPortCRCErrorThreshold OBJECT-TYPE
--    SYNTAX Integer32
--    MAX-ACCESS read-write
--    STATUS current
--    DESCRIPTION
--    "Controls the threshold at which CRC errors will cause an alarm to be sent
--    to the management system. The default value of 0 means that no alarm signal
--    shall be sent. Any positive integer will result in an alarm being sent when
--    the number of CRC errors exceeds the threshold."
--    DEFVAL { 0 }
--    ::= { drg600aPortEntry 24 }


--drg600aPortVlanGroupSupport OBJECT-TYPE
--    SYNTAX Integer32
--    MAX-ACCESS read-only
--    STATUS current
--    DESCRIPTION
--    "The maximum number of supported port VLAN groups. 0 indicates that port VLANs
--    are not supported."
--      ::= { drg600aPortEntry 25 }
	

-- *****************************************************************************
-- QoS configuration
--
-- *****************************************************************************
drg600aQosConfig OBJECT IDENTIFIER ::= {drg600aConfig 3} 

drg600aQosVlanPriorityNum OBJECT-TYPE
   SYNTAX Integer32
   MAX-ACCESS read-only
   STATUS current
   DESCRIPTION
  "Number of port vlan priority maps in the bridge."
    ::= { drg600aQosConfig 1 }

-- This table is of fixed size because there are only 8 possible VLAN priority values
drg600aQosVlanPriorityMapTable OBJECT-TYPE
  SYNTAX SEQUENCE OF Drg600aQosVlanPriorityMapEntry 
  MAX-ACCESS not-accessible
  STATUS current
  DESCRIPTION
  "A table of the mapping between the IEEE802.1p tag values and the egress queue priority"
    ::= { drg600aQosConfig 2 }

drg600aQosVlanPriorityMapEntry OBJECT-TYPE
   SYNTAX Drg600aQosVlanPriorityMapEntry
   MAX-ACCESS not-accessible
   STATUS current
   DESCRIPTION
      "One row of the table."
   INDEX { drg600aQosVlanPriorityMapIndex }
   ::= { drg600aQosVlanPriorityMapTable 1 }

Drg600aQosVlanPriorityMapEntry ::=
  SEQUENCE {
    drg600aQosVlanPriorityMapIndex Integer32,
    drg600aQosVlanPriorityMapPriority Integer32,
    drg600aQosVlanPriorityMapQueue Integer32
  }

drg600aQosVlanPriorityMapIndex OBJECT-TYPE
  SYNTAX Integer32 (1..8)
  MAX-ACCESS read-only
  STATUS current
  DESCRIPTION
  "A unique value greater than zero for each row"
    ::= { drg600aQosVlanPriorityMapEntry 1 }

drg600aQosVlanPriorityMapPriority OBJECT-TYPE
  SYNTAX Integer32 (0..7)
  MAX-ACCESS read-only
  STATUS current
  DESCRIPTION
  "Currently, There can only be 8 entries in port vlan priority map"
    ::= { drg600aQosVlanPriorityMapEntry 2 }

drg600aQosVlanPriorityMapQueue OBJECT-TYPE
  SYNTAX Integer32 (0..3)
  MAX-ACCESS read-write
  STATUS current
  DESCRIPTION
  "The mapped queue for the specific priority tag"
    ::= { drg600aQosVlanPriorityMapEntry 3 }

drg600aQosIpDSCPNum OBJECT-TYPE
   SYNTAX Integer32
   MAX-ACCESS read-only
   STATUS current
   DESCRIPTION
  "Number of port ip DSCP priority maps in the bridge."
    ::= { drg600aQosConfig 6 }

-- This table is of fixed size because there are only 64 possible DSCP values
drg600aQosIpDSCPMapTable OBJECT-TYPE
  SYNTAX SEQUENCE OF Drg600aQosIpDSCPMapEntry 
  MAX-ACCESS not-accessible
  STATUS current
  DESCRIPTION
  "A table of the mapping between the IP DSCP values and the egress queue priority"
    ::= { drg600aQosConfig 3 }

drg600aQosIpDSCPMapEntry OBJECT-TYPE
  SYNTAX Drg600aQosIpDSCPMapEntry
  MAX-ACCESS not-accessible
  STATUS current
  DESCRIPTION
  "One row of the table."
  INDEX { drg600aQosIpDSCPMapIndex }
    ::= { drg600aQosIpDSCPMapTable 1 }

Drg600aQosIpDSCPMapEntry ::=
  SEQUENCE {
    drg600aQosIpDSCPMapIndex Integer32,
    drg600aQosIpDSCPMapValue Integer32,
    drg600aQosIpDSCPMapQueue Integer32
  }

drg600aQosIpDSCPMapIndex OBJECT-TYPE
  SYNTAX Integer32 (1..64)
  MAX-ACCESS read-only
  STATUS current
  DESCRIPTION
  "A unique value greater than zero for each row"
    ::= { drg600aQosIpDSCPMapEntry 1 }

drg600aQosIpDSCPMapValue OBJECT-TYPE
  SYNTAX Integer32 (0..63)
  MAX-ACCESS read-only
  STATUS current
  DESCRIPTION
  "There can only be 64 entries in Diffserv priority map"
    ::= { drg600aQosIpDSCPMapEntry 2 }


drg600aQosIpDSCPMapQueue OBJECT-TYPE
  SYNTAX Integer32 (0..3)
  MAX-ACCESS read-write
  STATUS current
  DESCRIPTION
  "The mapped queue for the specific priority tag"
    ::= { drg600aQosIpDSCPMapEntry 3 }



-- *****************************************************************************
-- Selftest functionality. Used for production test or operation verification.
--
-- *****************************************************************************
selfTest OBJECT IDENTIFIER ::= { drg600aConfig 4 }

-- Nothing currently defined


-- *****************************************************************************
-- All notifications are defined here.  These can be sent as traps or as informs.
--
-- *****************************************************************************
notifyModuleState  NOTIFICATION-TYPE
  OBJECTS
  {
    productMacAddress,
    productIdentity,
    drg600aModuleStatus
  }
  STATUS      current
  DESCRIPTION
  "On reset, or after a change in state of any modules, this notification is
  sent to the network management system. This notification includes the details
  of all known modules."
    ::= { drg600aNotification 1 }


-- *****************************************************************************
-- drg600aGroups, drg600aCompliance define the groups and hence compliance of a
-- device
--
-- *****************************************************************************

drg600aGroups        OBJECT IDENTIFIER  ::=  { drg600aConformance 1 }
drg600aCompliance    OBJECT IDENTIFIER  ::=  { drg600aConformance 2 }
drg600aCompatibility OBJECT IDENTIFIER  ::=  { drg600aConformance 3 }

END
